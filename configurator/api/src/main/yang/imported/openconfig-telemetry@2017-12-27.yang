module openconfig-telemetry {

  yang-version "1";

  // namespace
  namespace "http://openconfig.net/yang/telemetry";

  prefix "oc-telemetry";

  // import some basic types
  import openconfig-inet-types { prefix oc-inet; }
  import openconfig-extensions { prefix oc-ext; }
  //import openconfig-telemetry-types { prefix oc-telemetry-types; }

  // meta
  organization "OpenConfig working group";

  contact
    "OpenConfig working group www.openconfig.net";

  description
    "Data model which creates the configuration for the telemetry
     systems and functions on the device.";

  oc-ext:openconfig-version "0.4.1";

  revision "2017-08-24" {
    description
      "Minor formatting fixes";
    reference "0.4.1";
  }

  revision "2017-02-20" {
    description
      "Fixes for YANG 1.0 compliance, add types module";
    reference "0.4.0";
  }

  revision "2016-04-05" {
    description
      "OpenConfig public release";
    reference "0.2.0";
  }

  // identity statements

  // typedef statements

  // grouping statements

  grouping telemetry-subscription-name-config {
       leaf subscription-name {
         type string;
       }
  }

  grouping telemetry-local-source-address-config {
         leaf local-source-address {
             type oc-inet:ipv4-address;
         }
  }

  grouping telemetry-sensor-group-config {
         leaf sensor-group-id {
             type string;
         }
  }

  grouping telemetry-stream-subscription-config {
         leaf sample-interval {
             type uint64;
         }

  }

  grouping telemetry-stream-destination-config {
        leaf destination-address {
        //choose ipv4
          type oc-inet:ipv4-address;
        }
        leaf destination-port {
          type uint16;
        }
  }

  grouping telemetry-sensor-specification {
      list telemetry-sensor-group {
        key "telemetry-sensor-group-id";

        leaf telemetry-sensor-group-id {
          type string;
        }
        uses telemetry-sensor-paths;
      }
  }

  grouping telemetry-sensor-paths {

      list telemetry-sensor-paths {
        key "telemetry-sensor-path";

        leaf telemetry-sensor-path {
          type string;
        }

      }
  }



  // data definition statements

  container telemetry-system {
    description
      "Top level configuration and state for the
       device's telemetry system.";

    container sensor-groups {
      description
        "Top level container for sensor-groups.";

      list sensor-group {
        key "sensor-group-id";
        description
          "List of telemetry sensory groups on the local
           system, where a sensor grouping represents a resuable
           grouping of multiple paths and exclude filters.";
  
        leaf sensor-group-id {
          //type leafref;
          type string{
            length 1..32;
          }
          description
            "Name or identifier for the sensor group itself.
             Will be referenced by other configuration specifying a
             sensor group";
        }

        container sensor-paths {
          description
            "Top level container to hold a set of sensor
             paths grouped together";

          list sensor-path {
            key "path";
            description
              "List of paths in the model which together
               comprise a sensor grouping. Filters for each path
               to exclude items are also provided.";

            leaf path {
              type string{
                length 1..250;
              }
              description
                "Path to a section of operational state of interest (the sensor).";
            }
          }
        }
      }
    }

    container destination-groups {
        description
          "Top level container for destination group configuration
           and state.";

        list destination-group {
          key "group-id";
          description
            "List of destination-groups. Destination groups allow the
             reuse of common telemetry destinations across the
             telemetry configuration. An operator references a
             set of destinations via the configurable
             destination-group-identifier.
             A destination group may contain one or more telemetry
             destinations";

          leaf group-id {
            type string{
              length 1..32;
            }
            description
              "Unique identifier for the destination group";
          }

          container destinations {
            description
              "The destination container lists the destination
               information such as IP address and port of the
               telemetry messages from the network element.";
            list destination {
              key "destination-address destination-port";
              description
                "List of telemetry stream destinations";

              leaf destination-address {
                type oc-inet:ip-address;
                description
                  "IP address of the telemetry stream destination";
              }

              leaf destination-port {
                type uint16;
                description
                  "Protocol (udp or tcp) port number for the telemetry
                   stream destination";
              }
            }
          }
        }
      }

    container subscriptions {
      description
        "This container holds information for both persistent
         and dynamic telemetry subscriptions.";

      container persistent {
        description
          "This container holds information relating to persistent
           telemetry subscriptions. A persistent telemetry
           subscription is configued locally on the device through
           configuration, and is persistent across device restarts or
           other redundancy changes.";

        list subscription {
          key "subscription-name";
          description
            "List of telemetry subscriptions. A telemetry
            subscription consists of a set of collection
            destinations, stream attributes, and associated paths to
            state information in the model (sensor data)";

          leaf subscription-name {
            type string{
              length 1..32;
            }
            description
              "User configured identifier of the telemetry
               subscription. This value is used primarily for
               subscriptions configured locally on the network
               element.";
          }

          container config {
            description
              "Config parameters relating to the telemetry
              subscriptions on the local device";

            leaf local-source-address {
              type oc-inet:ip-address;
              description
                "The IP address which will be the source of packets from
                 the device to a telemetry collector destination.";
            }

            //leaf protocol {
            //  type identityref {
            //    base oc-telemetry-types:STREAM_PROTOCOL;
            //  }
            //  description
            //    "Selection of the transport protocol for the telemetry
            //     stream.";
            //}

            //leaf encoding {
            //  type identityref {
            //    base oc-telemetry-types:DATA_ENCODING_METHOD;
            //  }
            //  description
             //   "Selection of the specific encoding or RPC framework
            //     for telemetry messages to and from the network element.";
            //}
          }

          container sensor-profiles {
            description
              "A sensor profile is a set of sensor groups or
              individual sensor paths which are associated with a
              telemetry subscription. This is the source of the
              telemetry data for the subscription to send to the
              defined collectors.";
            list sensor-profile {
              key "sensor-group";
              description
                "List of telemetry sensor groups used
                in the subscription";
              
              leaf sensor-group {
                type leafref {
		          path "/telemetry-system/sensor-groups/sensor-group/sensor-group-id";
                }
                description
                  "Reference to the sensor group which is used in the profile";
              }
		
              container config {
                description
                  "Configuration parameters related to the sensor
                  profile for a subscription";

                leaf sample-interval {
                  type uint64;
                  description
                    "Time in milliseconds between the device's sample of a
                     telemetry data source. For example, setting this to 100
                     would require the local device to collect the telemetry
                     data every 100 milliseconds. There can be latency or jitter
                     in transmitting the data, but the sample must occur at
                     the specified interval.
                     The timestamp must reflect the actual time when the data
                     was sampled, not simply the previous sample timestamp +
                     sample-interval.
                     If sample-interval is set to 0, the telemetry sensor
                     becomes event based. The sensor must then emit data upon
                     every change of the underlying data source.";
                }
              }
            }
          }

          container destination-groups {
            description
              "A subscription may specify destination addresses.
               If the subscription supplies destination addresses,
               the network element will be the initiator of the
               telemetry streaming, sending it to the destination(s)
               specified.
               If the destination set is omitted, the subscription
               preconfigures certain elements such as paths and
               sample intervals under a specified subscription ID.
               In this case, the network element will NOT initiate an
               outbound connection for telemetry, but will wait for
               an inbound connection from a network management
               system.
               It is expected that the network management system
               connecting to the network element will reference
               the preconfigured subscription ID when initiating
               a subscription.";

            list destination-group {
              key "group-id";
              description
                "Identifier of the previously defined destination
                 group";

              leaf group-id {
                type leafref {
		          path "/telemetry-system/destination-groups/destination-group/group-id";
                }
                description
                  "Reference to the sensor group which is used in the profile";
              }			
            }
          }
        }
      }
    }
  }
     

  // augment statements

  // rpc statements

  // notification statements

}
